--
-- Copyright (c) 2010 by Ruckus Wireless, Inc.
-- All Rights Reserved
--

RUCKUS-ROOT-MIB DEFINITIONS ::= BEGIN

IMPORTS
    enterprises,
    MODULE-IDENTITY
        FROM SNMPv2-SMI;

ruckusRootMIB MODULE-IDENTITY
    LAST-UPDATED "201212071100Z"
    ORGANIZATION "Ruckus Wireless, Inc."
    CONTACT-INFO
        "Ruckus Wireless, Inc.

		350 West Java Dr.
		Sunnyvale, CA 94089
		USA

		T: +1 (650) 265-4200
		F: +1 (408) 738-2065
		EMail: info@ruckuswireless.com
		Web: www.ruckuswireless.com"

    DESCRIPTION
        "Ruckus top level mib."
    ::= { enterprises 25053 }


-- Groups
--

ruckusObjects OBJECT IDENTIFIER  ::= { ruckusRootMIB 1 }

ruckusCommon OBJECT IDENTIFIER   ::= { ruckusObjects 1 }

ruckusCommonTCModule OBJECT IDENTIFIER      ::= { ruckusCommon 1 }

-- ruckusCommonHwInfoModule OBJECT IDENTIFIER  ::= { ruckusCommon 2 }

-- ruckusCommonSwInfoModule OBJECT IDENTIFIER  ::= { ruckusCommon 3 }

-- ruckusCommonDeviceModule OBJECT IDENTIFIER  ::= { ruckusCommon 4 }

-- ruckusCommonUpgradeModule OBJECT IDENTIFIER ::= { ruckusCommon 5 }

-- ruckusCommonWLANModule OBJECT IDENTIFIER    ::= { ruckusCommon 6 }

-- ruckusCommonDHCPModule OBJECT IDENTIFIER    ::= { ruckusCommon 7 }

-- ruckusCommonPPPOEModule OBJECT IDENTIFIER   ::= { ruckusCommon 8 }

-- ruckusCommonAdapterModule OBJECT IDENTIFIER ::= { ruckusCommon 9 }

-- ruckusCommonQosModule OBJECT IDENTIFIER     ::= { ruckusCommon 10 }

-- ruckusCommonSystemModule OBJECT IDENTIFIER  ::= { ruckusCommon 11 }

-- ruckusCommonRadioModule OBJECT IDENTIFIER   ::= { ruckusCommon 12 }

-- ruckusCommonEthModule OBJECT IDENTIFIER     ::= { ruckusCommon 13 }

-- ruckusCommonL2TPModule OBJECT IDENTIFIER    ::= { ruckusCommon 14 }

-- ruckusCommonWLINKModule OBJECT IDENTIFIER   ::= { ruckusCommon 15 }

ruckus OBJECT IDENTIFIER   ::= { ruckusObjects 3 }

ruckusSystemModule OBJECT IDENTIFIER      ::= { ruckus 1 }

ruckusWLANModule OBJECT IDENTIFIER        ::= { ruckus 2 }

ruckusTTGModule OBJECT IDENTIFIER        ::= { ruckus 3 }

ruckusEvents OBJECT IDENTIFIER    ::= { ruckusRootMIB 2 }

ruckusProducts OBJECT IDENTIFIER  ::= { ruckusRootMIB 3 }

END
